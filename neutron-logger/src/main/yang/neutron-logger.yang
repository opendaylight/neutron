module neutron-logger {
    yang-version 1;
    namespace "urn:opendaylight:params:xml:ns:yang:neutron:logger";
    prefix "neutron-logger";

    import config { prefix config; revision-date 2013-04-05; }
    import opendaylight-md-sal-binding { prefix md-sal-binding; revision-date 2013-10-28;}

    description
        "Service definition for Neutron event logger";

    revision "2016-06-09" {
        description
            "Initial revision";
    }

    identity neutron-logger {
        base config:module-type;
        config:java-name-prefix NeutronLogger;
    }

    augment "/config:modules/config:module/config:configuration" {
        case neutron-logger {
            when "/config:modules/config:module/config:type = 'neutron-logger'";
            container data-broker {
                uses config:service-ref {
                    refine type {
                        mandatory true;
                        config:required-identity md-sal-binding:binding-async-data-broker;
                    }
                }
            }
        }
    }
}
