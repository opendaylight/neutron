/*
 * Copyright (c) 2015 Ericsson India Global Services Pvt Ltd. and others.
 * All rights reserved.
 *
 * This program and the accompanying materials are made available under the
 * terms of the Eclipse Public License v1.0 which accompanies this distribution,
 * and is available at http://www.eclipse.org/legal/epl-v10.html
 */

module neutron-bgpvpns {

    yang-version 1;

    namespace "urn:opendaylight:neutron-bgpvpns";

    prefix neutron-bgpvpns;

    import ietf-yang-types { prefix "yang"; }
    import neutron-attrs { prefix "attrs"; }

    organization "OpenDaylight Neutron Group";

    contact "Vishal Thapar <vishal.thapar@ericsson.com>";

    description "This YANG module defines Openstack Liberty Neutron BGPVPN model";

    revision "2015-09-03" {
        description
                "Initial version of Openstack Neutron Liberty BGPVPN model.";
    }

    identity bgpvpn-type-base {
        description
                "Base Network type for all Bgpvpn type identifiers.";
    }

    identity bgpvpn-type-l2 {
        base bgpvpn-type-base;
        description
                "L2 bgpvpn type identity.";
    }
    identity bgpvpn-type-l3 {
        base bgpvpn-type-base;
        description
                "L3 bgpvpn type identity.";
    }

    typedef bgpvpn-type {
        type identityref {
            base bgpvpn-type-base;
        }
        description
                "This type is used to refer to a Bgpvpn Type.";
    }

    grouping bgpvpn-attributes {
        leaf type {
            type bgpvpn-type;
            description "selection of the type of VPN. e.g. l3 or l2";
        }
        leaf technique {
            type string;
            description "selection of technique used to implement VPN";
        }
        leaf-list route-targets {
            type string;
            description "route-targets";
        }
        leaf-list import-targets {
            type string;
            description "import RTs";
        }
        leaf-list export-targets {
            type string;
            description "export RTs";
        }
        leaf-list route-distinguishers {
            type string;
            description "list route-distinguishers";
        }
        leaf vni {
            type uint32;
            description "globally assigned VxLanId";
        }
        leaf auto-aggregate {
            type boolean;
            description "auto-aggregate enabled or not";
            default "false";
        }
    }

    grouping bgpvpns-attributes {
        container bgpvpns {
            list bgpvpn {
                key "uuid";
                uses attrs:base-attributes;
                uses attrs:admin-attributes;
                uses bgpvpn-attributes;
            }
        }
    }
}
