/*
 * Copyright (c) 2015 Brocade Communications Systems, Inc. and others.  All rights reserved.
 *
 * This program and the accompanying materials are made available under the
 * terms of the Eclipse Public License v1.0 which accompanies this distribution,
 * and is available at http://www.eclipse.org/legal/epl-v10.html
 */
module neutron-provider {

    yang-version 1;

    namespace "urn:opendaylight:neutron-provider";

    prefix neutron-provider;

    import neutron-networks { prefix "networks"; }

    organization "OpenDaylight Neutron Group";

    contact "J. Gregory Hall <ghall@brocade.com>, Kiran Sreenivasa <kkoushik@brocade.com>";

    description "This YANG module defines provider attributes that are used by Openstack
        Juno House Neutron YANG modules.";

    revision "2014-10-02" {
        description
                "Initial version of provider attributes used by OpenStack Ice House Neutron
                models";
    }

    grouping provider-attributes {
        leaf physical-network {
            type string;
            description "The physical network where this network object is implemented.
                        The Networking API v2.0 does not provide a way to list available
                        physical networks. For example, the Open vSwitch plug-in configuration
                        file defines a symbolic name that maps to specific bridges on
                        each Compute host.";
        }

        leaf network-type {
            type networks:network-type;
            description "The type of physical network that maps to this network resource.";
        }
        leaf segmentation-id {
            type string;
            description "An isolated segment on the physical network. The network-type
                        attribute defines the segmentation model. For example, if network-type
                        is vlan, this ID is a vlan identifier. If network-type is gre,
                        this ID is a gre key.";
        }
        leaf segmentation-index {
            type uint32;
            description "A hidden counter to act as a key, because
                        segmentation id is not required.";
        }
    }
}
