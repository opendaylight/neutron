/*
 *
 * This program and the accompanying materials are made available under the
 * terms of the Eclipse License v1.0 which accompanies this distribution,
 * and is available at http://www.eclipse.org/legal/epl-v10.html
 */

module neutron-bgpvpn-router-association {

    yang-version 1;

    namespace "urn:opendaylight:neutron-bgpvpn-router-association";

    prefix neutron-bgpvpn-router-association;

    import ietf-yang-types { prefix "yang"; }
    import neutron-attrs { prefix "attrs"; }

    organization "OpenDaylight Neutron Group";

    contact "Manjunath N P <manjupayala@gmail.com>";

    description "This YANG module defines Openstack Liberty Neutron BGPVPN Router Association model";

    revision "2019-05-02" {
        description
            "Initial version of Openstack Neutron Liberty BGPVPN Router Association model.";
    }

    grouping bgpvpn-router-association-attributes {
        leaf bgpvpn-id {
            type yang:uuid;
        }
        leaf router-id {
            type yang:uuid;
            description "Router associated to this VPN.";
        }
    }

    grouping bgpvpn-router-associations-attributes {
        container bgpvpn-router-associations {
            list bgpvpn-router-association {
                key "uuid";
                uses attrs:base-attributes;
                uses attrs:admin-attributes;
                uses bgpvpn-router-association-attributes;
            }
        }
    }
}
