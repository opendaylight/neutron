/*
 * Copyright (c) 2015 Brocade Communications Systems, Inc. and others.  All rights reserved.
 *
 * This program and the accompanying materials are made available under the
 * terms of the Eclipse Public License v1.0 which accompanies this distribution,
 * and is available at http://www.eclipse.org/legal/epl-v10.html
 */
module neutron-provider-ext {

    yang-version 1;

    namespace "urn:opendaylight:neutron-provider-ext";

    prefix neutron-provider-ext;

    import neutron { prefix "neutron"; }
    import neutron-provider { prefix "provider"; }
    import yang-ext { prefix "ext"; }

    organization "OpenDaylight Neutron Group";

    contact "J. Gregory Hall <ghall@brocade.com>, Kiran Sreenivasa <kkoushik@brocade.com>";

    description "This YANG module defines provider model extensions that are used by Openstack
        Ice House Neutron YANG modules.";

    revision "2014-10-02" {
        description
                "Initial version of provider model extensions used by OpenStack Ice House Neutron
                models";
    }

    augment "/neutron:neutron/neutron:networks/neutron:network"{
        description "This module augments the networks container
                in the neutron-networks module with provider information.";
        ext:augment-identifier "network-provider-extension";
        list segments {
            description "List of provider network(s) associated with this network.";
            key segmentation-index;
            uses provider:provider-attributes;
        }
        uses provider:provider-attributes;
    }
}
