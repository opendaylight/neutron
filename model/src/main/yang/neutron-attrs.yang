/*
 * Copyright (c) 2015 Brocade Communications Systems, Inc. and others.  All rights reserved.
 *
 * This program and the accompanying materials are made available under the
 * terms of the Eclipse Public License v1.0 which accompanies this distribution,
 * and is available at http://www.eclipse.org/legal/epl-v10.html
 */
module neutron-attrs {

    yang-version 1;

    namespace "urn:opendaylight:neutron-attrs";

    prefix neutron-attrs;

    import ietf-yang-types { prefix "yang"; revision-date "2013-07-15";}

    organization "OpenDaylight Neutron Group";

    contact "J. Gregory Hall <ghall@brocade.com>, Kiran Sreenivasa <kkoushik@brocade.com>";

    description "This YANG module defines groupings that are used
        by OpenDaylight Neutron YANG modules.";

    revision "2015-07-12" {
        description
                "OpenDaylight Beryllium release";
    }

    grouping id-attributes {
        leaf uuid {
            type yang:uuid;
            description "UUID to index this neutron object.";
        }
        leaf tenant-id {
            status deprecated;
            type yang:uuid;
            description "The UUID of the tenant that will own the object.";
        }

        leaf project-id {
            type string {
                length "0..255";
            }
            description "The id of the project.";
        }

        leaf revision-number {
            type int64;
            description "The revision number of the resource. Used as monotonic
                         counter that is updated whenever an object is updated
                         on neutron server";
        }
    }

    grouping base-attributes {
        uses id-attributes;
        leaf name {
            type string;
            description "Human-readable name for the item. Might not be unique.";
        }
    }

    grouping admin-attributes {
        leaf admin-state-up {
            type boolean;
            description "The administrative state of the object, which is up (true) or
                        down (false).";
        }
        leaf status {
            type string;
            status deprecated;
            description "The object status.";
        }
    }

    grouping operational-attributes {
        list status {
            key "uuid";
            leaf uuid {
                type yang:uuid;
                description "UUID to index this neutron object.";
            }
            leaf status {
                type string;
                description "The object status.";
            }
        }
    }
}
