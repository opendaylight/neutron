/*
 * Copyright (c) 2015 Brocade Communications Systems, Inc. and others.  All rights reserved.
 *
 * This program and the accompanying materials are made available under the
 * terms of the Eclipse Public License v1.0 which accompanies this distribution,
 * and is available at http://www.eclipse.org/legal/epl-v10.html
 */
module neutron-networks {

    yang-version 1;

    namespace "urn:opendaylight:neutron-networks";

    prefix neutron-networks;

    import ietf-yang-types { prefix "yang"; }
    // It requires rfc6991 (revision 2013-07-15), but odl don't have it, so this patch verify build will fail.
    import ietf-inet-types { prefix "inet"; revision-date 2010-09-24; }
    import neutron-attrs { prefix "attrs"; }

    organization "OpenDaylight Neutron Group";

    contact "J. Gregory Hall <ghall@brocade.com>, Kiran Sreenivasa <kkoushik@brocade.com>";

    description "This YANG module defines Openstack Juno House Neutron Network model";

    revision "2014-10-02" {
        description
                "Initial version of Openstack Neutron Ice House Network model.";
    }
    identity network-type-base {
        description
                "Base Network type for all Network type identifiers.";
    }

    identity network-type-flat {
        base network-type-base;
        description
                "Flat network type identity.";
    }
    identity network-type-vlan {
        base network-type-base;
        description
                "VLAN network type identity.";
    }
    identity network-type-vxlan {
        base network-type-base;
        description
                "VXLAN network type identity.";
    }
    identity network-type-gre {
        base network-type-base;
        description
                "GRE network type identity.";
    }

    typedef network-type {
        type identityref {
            base network-type-base;
        }
        description
                "This type is used to refer to a Network Type.";
    }
    grouping network-attrs {

        leaf-list subnets {
            description "The associated subnets.";
            type yang:uuid;
        }

        leaf shared {
            type boolean;
            default "false";
            description "Indicates whether this network or subnet is shared across all
                        tenants. By default, only administrative users can change this
                        value.";
        }

    }

    grouping networks-attributes {
        container networks {
            list network {

                description "A network is a virtual isolated layer-2 broadcast domain which
                            is typically reserved to the tenant who created it, unless the
                            network has been explicitly configured to be shared. Tenants can
                            create multiple networks, until they reach the thresholds specified
                            by per-tenant Quotas. The network is the principal entity for 
                            the Neutron API. Ports and Subnets must always be associated 
                            with a network.";

                key "uuid";
                uses attrs:base-attrs;
                uses attrs:admin-attrs;
                uses network-attrs;
            }
        }
    }
}
