/*
 * Copyright (c) 2015 Hewlett-Packard Development Company and others.  All rights reserved.
 *
 * This program and the accompanying materials are made available under the
 * terms of the Eclipse Public License v1.0 which accompanies this distribution,
 * and is available at http://www.eclipse.org/legal/epl-v10.html
 */
module neutron-l2gateways{
    yang-version 1;
    namespace "urn:opendaylight:neutron-l2gateways";
    prefix neutron-l2gateways;

    import ietf-yang-types { prefix "yang"; }
    import neutron-attrs { prefix "attrs"; }

    organization "OpenDaylight Neutron Group";

    description "This YANG module defines l2gateway objects that are used by
                 Openstack kilo Neutron YANG modules.";

    revision "2015-07-12" {
        description
                "Initial version of l2gateway group objects used by OpenStack
                 kilo Neutron models";
    }

    grouping l2gateway-connection-attributes {
        leaf l2gateway-id {
            type yang:uuid;
        }
        leaf network-id {
            type yang:uuid;
        }
        leaf segment-id {
            type int32;
        }
        leaf port-id {
            type yang:uuid;
        }
    }

    grouping l2gateway-attributes {
        list devices {
            description "Description of devices.";
            key "uuid";
            leaf uuid {
                type yang:uuid;
            }
            leaf device-name {
                type string;
            }
            list interfaces {
                description "Description of interfaces";
                key interface-name;
                leaf interface-name {
                    type string;
                }
                leaf-list segmentation-ids {
                    description "Description of segmentations";
                    type int32;
                }
            }
        }
     }

   grouping l2gateways-attributes {
        container l2gateways {
            list l2gateway {
                description "l2gateway description ";
                key "uuid";
                uses attrs:base-attributes;
                uses l2gateway-attributes;
            }
        }
    }

    grouping l2gateway-connections-attributes{
         container l2gatewayConnections {
            list l2gatewayConnection {
                description "l2gateway connection description ";
                key "uuid";
                uses attrs:id-attributes;
                uses l2gateway-connection-attributes;
            }
        }
     }

}
