/*
 * Copyright (c) 2015 Brocade Communications Systems, Inc. and others.  All rights reserved.
 *
 * This program and the accompanying materials are made available under the
 * terms of the Eclipse Public License v1.0 which accompanies this distribution,
 * and is available at http://www.eclipse.org/legal/epl-v10.html
 */
module neutron-metering {

    yang-version 1;

    namespace "urn:opendaylight:neutron-metering";

    prefix neutron-metering;

    import ietf-yang-types { prefix "yang"; }
    import ietf-inet-types { prefix "inet"; revision-date 2013-07-15; }
    import neutron-attrs { prefix "attrs"; }
    import neutron-constants { prefix "constants"; }

    organization "OpenDaylight Neutron Group";

    contact "J. Gregory Hall <ghall@brocade.com>, Kiran Sreenivasa <kkoushik@brocade.com>";

    description "This YANG module defines Openstack Neutron Metering attributes";

    revision "2015-07-12" {
        description
                "OpenDaylight Beryllium release";
    }

    grouping metering-label-attributes {
        description "OpenStack Layer3 Metering label information.";
        leaf shared {
            type boolean;
            description "Indicates whether this metering label is shared across all tenants.";
            default "false";
        }
    }

    grouping metering-rule-attributes {
        description "OpenStack Layer3 Metering label rules.";
        leaf uuid {
            type yang:uuid;
            description "Metering Rule ID.";
        }
        leaf tenant-id {
            type yang:uuid;
            description "The UUID of the tenant that will own the object.";
        }
        leaf direction {
            type identityref {
                base "constants:direction-base";
            }
            description "The direction in which metering rule is applied.";
        }
        leaf metering-label-id {
            type yang:uuid;
            description "Metering Label ID to associate with this metering rule.";
        }
        leaf remote-ip-prefix {
            description "The remote IP prefix to be associated with this metering rule. packet.";
            type inet:ip-prefix;
        }
        leaf excluded {
            type boolean;
            description "Specify whether the remote_ip_prefix
                will be excluded or not from traffic counters of
                the metering label, ie: to not count the traffic
                of a specific IP address of a range.";
            default "false";
        }
    }

    grouping metering-labels-attributes {
        container metering-labels {
            description "Container for metering labels.";
            list metering-label {
                key "uuid";
                uses attrs:base-attributes;
                uses metering-label-attributes;
                description "List of Metering Labels.";
            }
        }
    }

    grouping metering-rules-attributes {
        container metering-rules {
            description " Container for metering rules.";
            list metering-rule {
                key "uuid";
                uses metering-rule-attributes;
                description "List of Metering Rules.";
            }
        }
    }
}
