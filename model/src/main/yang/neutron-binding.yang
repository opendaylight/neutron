/*
 * Copyright (c) 2015 IBM Corporation.  All rights reserved.
 *
 * This program and the accompanying materials are made available under the
 * terms of the Eclipse Public License v1.0 which accompanies this distribution,
 * and is available at http://www.eclipse.org/legal/epl-v10.html
 */
module neutron-binding {

    yang-version 1;

    namespace "urn:opendaylight:neutron-binding";

    prefix neutron-binding;

    import yang-ext { prefix "ext"; }
    import neutron { prefix "neutron"; }


    organization "OpenDaylight Neutron Group";

    contact "Ryan Moats <rmoats@us.ibm.com>";

    description "This YANG module defines binding attributes that are used
        by OpenDaylight Neutron YANG modules.";

    revision "2015-07-12" {
        description
                "OpenDaylight Beryllium release";
    }

    grouping binding-attributes {
        leaf host-id {
            type string;
            description "The ID of the host where the port is allocated. In some cases,
                        different implementations can run on different hosts.";
        }

        list vif-details {
            description "A dictionary that enables the application to pass information
                        about functions that the Networking API provides. To enable or
                        disable port filtering features such as security group and anti-MAC/IP
                        spoofing, specify port-filter: True or port-filter: False ";
            // work around: "key" as leaf name in list can't be used due to java code
            // generation. getKey() method is reserved for to retrieve key of the list
            // and get<Name>() is also generated as a getter. it results in name
            // collision.
            // please see BindingGeneratorImpl#typeBuildersToGenTypes() for details.
            // This isn't easily fixed as it's deeply hard-coded.
            key details-key;
            leaf details-key {
                type string;
            }
            leaf value {
                type string;
            }
        }
        leaf vif-type {
            type string;
        }
        leaf vnic-type {
            type string;
        }
        container profile {
            leaf-list capabilities {
                type string;
            }
        }
    }

    augment "/neutron:neutron/neutron:ports/neutron:port" {
        description "This module augments the ports container in
                the neutron-ports module with binding information.";
        ext:augment-identifier "port-binding-extension";
        uses binding-attributes;
    }
}
