module neutron-transcriber-impl {
    yang-version 1;
    namespace "urn:opendaylight:params:xml:ns:yang:neutron:transcriber:impl";
    prefix "neutron-transcriber-impl";

    import config { prefix config; revision-date 2013-04-05; }
    import opendaylight-md-sal-binding { prefix md-sal-binding; revision-date 2013-10-28;}

    description
        "Service definition for southbound project";

    revision "2014-12-10" {
        description
            "Initial revision";
    }

    identity neutron-transcriber-impl {
        base config:module-type;
        config:java-name-prefix NeutronTranscriberImpl;
    }

    augment "/config:modules/config:module/config:configuration" {
        case neutron-transcriber-impl {
            when "/config:modules/config:module/config:type = 'neutron-transcriber-impl'";
            container broker {
                uses config:service-ref {
                    refine type {
                        mandatory true;
                        config:required-identity md-sal-binding:binding-broker-osgi-registry;
                    }
                }
            }
        }
    }
}
